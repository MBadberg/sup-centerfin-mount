import os

import FreeCAD as App
from FreeCAD import Vector
import Part
import Mesh

try:
    import FreeCADGui as Gui
except Exception:
    Gui = None

try:
    from PySide import QtGui
except Exception:
    QtGui = None


print("\n" + "=" * 75)
print("  STARTING FIN NEGATIVE HOLDER MACRO")
print("=" * 75 + "\n")


# -----------------------------------------------------------------------------
# Parameter
# -----------------------------------------------------------------------------

fin_stl_path = ""  # Optional absolute path to the downloaded Thingiverse STL.
mesh_tolerance = 0.10
fit_clearance = 0.35

shell_wall = 7.0
shell_back_wall = 9.0
shell_top_wall = 8.0
shell_bottom_wall = 8.0

base_margin_x = 20.0
base_margin_y = 34.0
base_thickness = 8.0

strap_slot_length = 38.0
strap_slot_width = 8.0
strap_slot_margin = 18.0

pin_hole_diameter = 6.5
pin_x_ratio = 0.24
pin_z_ratio = 0.72

rib_width = 18.0
rib_depth = 10.0

outer_fillet = 4.0
base_fillet = 6.0
opening_fillet = 2.0


# -----------------------------------------------------------------------------
# Helpers
# -----------------------------------------------------------------------------

def macro_dir():
    path = globals().get("__file__", "")
    if path:
        return os.path.dirname(os.path.abspath(path))
    try:
        return App.getUserMacroDir(True)
    except Exception:
        return os.getcwd()


def create_document(name):
    existing = App.ActiveDocument
    if existing is not None:
        App.closeDocument(existing.Name)
    doc = App.newDocument(name)
    print("✓ Dokument erstellt: %s" % doc.Name)
    return doc


def safe_fillet(shape, radius, edge_filter=None):
    if radius <= 0:
        return shape

    try:
        edges = [edge for edge in shape.Edges if edge_filter is None or edge_filter(edge)]
        if not edges:
            return shape
        return shape.makeFillet(radius, edges)
    except Exception as exc:
        print("  ⚠ Fillet fehlgeschlagen: %s" % exc)
        return shape


def translated_copy(shape, vector):
    result = shape.copy()
    result.translate(vector)
    return result


def ensure_short_axis_y(shape):
    bbox = shape.BoundBox
    lengths = {"X": bbox.XLength, "Y": bbox.YLength, "Z": bbox.ZLength}
    shortest = min(lengths, key=lengths.get)

    aligned = shape.copy()
    if shortest == "X":
        aligned.rotate(Vector(0, 0, 0), Vector(0, 0, 1), 90)
    elif shortest == "Z":
        aligned.rotate(Vector(0, 0, 0), Vector(1, 0, 0), -90)
    return aligned


def ensure_long_axis_z(shape):
    bbox = shape.BoundBox
    lengths = {"X": bbox.XLength, "Y": bbox.YLength, "Z": bbox.ZLength}
    longest = max(lengths, key=lengths.get)

    aligned = shape.copy()
    if longest == "X":
        aligned.rotate(Vector(0, 0, 0), Vector(0, 1, 0), 90)
    elif longest == "Y":
        aligned.rotate(Vector(0, 0, 0), Vector(1, 0, 0), -90)
    return aligned


def orient_fin(shape):
    aligned = ensure_short_axis_y(shape)
    aligned = ensure_long_axis_z(aligned)
    bbox = aligned.BoundBox
    return translated_copy(aligned, Vector(-bbox.XMin, -bbox.YMin, -bbox.ZMin))


def find_fin_stl():
    if fin_stl_path and os.path.isfile(fin_stl_path):
        return fin_stl_path

    search_root = macro_dir()
    candidates = []
    for name in os.listdir(search_root):
        candidate = os.path.join(search_root, name)
        if name.lower().endswith(".stl") and os.path.isfile(candidate):
            candidates.append(candidate)

    if len(candidates) == 1:
        print("✓ STL automatisch gefunden: %s" % candidates[0])
        return candidates[0]

    if Gui is not None and QtGui is not None:
        selected, _ = QtGui.QFileDialog.getOpenFileName(
            None,
            "Finnen-STL auswählen (Thingiverse thing:2994255)",
            search_root,
            "STL Files (*.stl)",
        )
        if selected:
            print("✓ STL ausgewählt: %s" % selected)
            return selected

    raise RuntimeError(
        "Keine STL gefunden. Lade die Standard-Finne von thing:2994255 herunter "
        "und lege die STL neben das Makro oder setze fin_stl_path."
    )


def load_fin_solid(stl_path):
    print("Lade STL: %s" % stl_path)
    mesh = Mesh.Mesh(stl_path)
    if mesh.CountFacets == 0:
        raise RuntimeError("Die STL enthält keine Flächen.")

    shape = Part.Shape()
    shape.makeShapeFromMesh(mesh.Topology, mesh_tolerance)
    shell = Part.makeShell(shape.Faces)
    solid = Part.makeSolid(shell)
    return solid.removeSplitter()


def expand_for_clearance(shape):
    if fit_clearance <= 0:
        return shape

    try:
        expanded = shape.makeOffsetShape(fit_clearance, 0.05, fill=True)
        return expanded.removeSplitter()
    except Exception as exc:
        print("  ⚠ Offset für Passspiel fehlgeschlagen, nutze exakte STL: %s" % exc)
        return shape


def make_slot(center_x, center_y, total_length, total_width, cut_height):
    radius = total_width / 2.0
    straight = max(total_length - total_width, 0.0)

    front = Part.makeCylinder(radius, cut_height, Vector(center_x, center_y - straight / 2.0, -1.0), Vector(0, 0, 1))
    rear = Part.makeCylinder(radius, cut_height, Vector(center_x, center_y + straight / 2.0, -1.0), Vector(0, 0, 1))

    if straight > 0:
        bridge = Part.makeBox(
            total_width,
            straight,
            cut_height,
            Vector(center_x - radius, center_y - straight / 2.0, -1.0),
        )
        return front.fuse(rear).fuse(bridge)

    return front.fuse(rear)


def build_negative_holder(fin_cavity):
    cavity_box = fin_cavity.BoundBox

    shell_origin = Vector(
        cavity_box.XMin - shell_wall,
        cavity_box.YMin,
        base_thickness,
    )
    shell = Part.makeBox(
        cavity_box.XLength + (2.0 * shell_wall),
        cavity_box.YLength + shell_back_wall,
        cavity_box.ZLength + shell_top_wall + shell_bottom_wall,
        shell_origin,
    )

    return shell.cut(fin_cavity)


def build_base(shell_shape):
    shell_box = shell_shape.BoundBox
    base = Part.makeBox(
        shell_box.XLength + (2.0 * base_margin_x),
        shell_box.YLength + (2.0 * base_margin_y),
        base_thickness,
        Vector(shell_box.XMin - base_margin_x, shell_box.YMin - base_margin_y, 0),
    )

    return safe_fillet(
        base,
        base_fillet,
        lambda edge: edge.BoundBox.ZMax >= base_thickness - 0.01,
    )


def build_ribs(shell_shape, base_shape):
    shell_box = shell_shape.BoundBox
    base_box = base_shape.BoundBox

    left_rib = Part.makeBox(
        rib_width,
        rib_depth,
        shell_box.ZLength * 0.45,
        Vector(shell_box.XMin + shell_wall, shell_box.YMax, base_thickness),
    )

    right_rib = Part.makeBox(
        rib_width,
        rib_depth,
        shell_box.ZLength * 0.45,
        Vector(shell_box.XMax - shell_wall - rib_width, shell_box.YMax, base_thickness),
    )

    back_rib = Part.makeBox(
        shell_box.XLength * 0.50,
        rib_depth,
        shell_box.ZLength * 0.28,
        Vector(
            shell_box.XMin + (shell_box.XLength * 0.25),
            base_box.YMax - base_margin_y,
            base_thickness,
        ),
    )

    ribs = left_rib.fuse(right_rib).fuse(back_rib)
    return safe_fillet(
        ribs,
        2.0,
        lambda edge: edge.BoundBox.ZMax > base_thickness + 0.01,
    )


def build_pin_hole(shell_shape, cavity_shape):
    cavity_box = cavity_shape.BoundBox
    shell_box = shell_shape.BoundBox

    pin_x = cavity_box.XMin + (cavity_box.XLength * pin_x_ratio)
    pin_z = cavity_box.ZMin + (cavity_box.ZLength * pin_z_ratio)

    return Part.makeCylinder(
        pin_hole_diameter / 2.0,
        shell_box.YLength + 2.0,
        Vector(pin_x, shell_box.YMin - 1.0, pin_z),
        Vector(0, 1, 0),
    )


def build_strap_slots(base_shape):
    base_box = base_shape.BoundBox
    front_x = base_box.XMin + strap_slot_margin
    rear_x = base_box.XMax - strap_slot_margin
    center_y = base_box.Center.y
    cut_height = base_box.ZLength + 2.0

    front = make_slot(front_x, center_y, strap_slot_length, strap_slot_width, cut_height)
    rear = make_slot(rear_x, center_y, strap_slot_length, strap_slot_width, cut_height)
    return front.fuse(rear)


# -----------------------------------------------------------------------------
# Build
# -----------------------------------------------------------------------------

def run():
    stl_path = find_fin_stl()
    doc = create_document("FinNegativeHolder")

    fin_solid = orient_fin(load_fin_solid(stl_path))
    fin_cavity = expand_for_clearance(fin_solid)
    fin_cavity_box = fin_cavity.BoundBox
    fin_cavity = translated_copy(
        fin_cavity,
        Vector(
            shell_wall - fin_cavity_box.XMin,
            -fin_cavity_box.YMin,
            (base_thickness + shell_bottom_wall) - fin_cavity_box.ZMin,
        ),
    )
    fin_bbox = fin_cavity.BoundBox

    print("Erzeuge Negativ-Halter aus realer Finnenform...")
    holder_shell = build_negative_holder(fin_cavity)
    holder_box = holder_shell.BoundBox
    holder_shell = safe_fillet(
        holder_shell,
        outer_fillet,
        lambda edge: edge.BoundBox.YMin >= holder_box.YMax - shell_back_wall - 0.01,
    )

    holder_box = holder_shell.BoundBox
    holder_shell = safe_fillet(
        holder_shell,
        opening_fillet,
        lambda edge: abs(edge.BoundBox.YMin - holder_box.YMin) < 0.01,
    )

    final_base = build_base(holder_shell)
    ribs = build_ribs(holder_shell, final_base)
    pin_hole = build_pin_hole(holder_shell, fin_cavity)
    strap_slots = build_strap_slots(final_base)

    result = final_base.fuse(holder_shell).fuse(ribs)
    result = result.cut(pin_hole)
    result = result.cut(strap_slots)

    part_obj = doc.addObject("Part::Feature", "FinNegativeHolder")
    part_obj.Shape = result
    part_obj.Label = "SUP Fin Negative Holder"

    reference_obj = doc.addObject("Part::Feature", "ReferenceFin")
    reference_obj.Shape = fin_cavity
    reference_obj.Label = "Reference Fin Cavity"
    if Gui is not None:
        reference_obj.ViewObject.Visibility = False

    doc.recompute()

    if Gui is not None:
        try:
            part_obj.ViewObject.DisplayMode = "Flat Lines"
            part_obj.ViewObject.ShapeColor = (0.20, 0.45, 0.85)
            Gui.SendMsgToActiveView("ViewFitAll")
        except Exception as exc:
            print("  ⚠ Ansicht konnte nicht angepasst werden: %s" % exc)

    print("\n" + "=" * 75)
    print("  PARAMETER")
    print("=" * 75)
    print("STL: %s" % stl_path)
    print("Fit clearance: %.2f mm" % fit_clearance)
    print("Pin hole diameter: %.2f mm" % pin_hole_diameter)
    print("Strap slot size: %.2f x %.2f mm" % (strap_slot_length, strap_slot_width))
    print("Fin bounding box: %.2f x %.2f x %.2f mm" % (fin_bbox.XLength, fin_bbox.YLength, fin_bbox.ZLength))
    print("✓ Fertig: Negativ-Halter erzeugt und im Dokument angezeigt.")
    print("=" * 75 + "\n")


try:
    run()
except Exception as exc:
    message = "FinNegativeHolder fehlgeschlagen: %s\n" % exc
    print("❌ " + message)
    try:
        App.Console.PrintError(message)
    except Exception:
        pass
